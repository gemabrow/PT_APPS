(defun c:beam_spt ()
                   ;SET MAXIMUM SPACING
                     (setq maxspa 42)  
                     (setq scale (getvar "userr1"))
                     (setvar "cmdecho" 0)
   (if (= (cdr (assoc '40 (tblsearch "style" (getvar "textstyle")))) 0.0) ;RESET TEXT HT TO 1/8" IF CURRENT HT IS 0"
        (command "style" "ROMANS" "ROMANS.shx,SPECIAL.shx" (/ (getvar "userr1") 8.0) 0.9 0 "N" "N" "N")  
   )
   (input)
   ;ASSIGN ASSOC LIST CONTAINING DRAPE FACTORS KEYED BY SPACETYPE
   (cond ((= spacetype "10")   
          (setq factlist '((1 0.3125) (2 0.14 0.56) (3 0.08 0.31 0.7)
             (4 0.05 0.2 0.45 0.8) (5 0.03 0.14 0.31 0.56 0.86)
             (6 0.03 0.11 0.23 0.4 0.63 0.88)
             (7 0.02 0.08 0.17 0.31 0.49 0.7 0.92)
             (8 0.02 0.06 0.14 0.25 0.39 0.56 0.76 0.96))
          )
         ) 
         ((= spacetype "12")
          (setq factlist '((1 0.30) (2 0.13 0.53) (3 0.08 0.30 0.68)
             (4 0.05 0.19 0.43 0.77) (5 0.03 0.13 0.30 0.53 0.83)
             (6 0.02 0.10 0.22 0.39 0.61 0.88)
             (7 0.02 0.08 0.17 0.30 0.47 0.68 0.91)
             (8 0.02 0.06 0.13 0.24 0.37 0.53 0.73 0.93))
          )
         )
         ((= spacetype "20")
          (setq factlist '((1 0.20) (2 0.12 0.49) (3 0.07 0.28 0.63)
             (4 0.04 0.18 0.40 0.71) (5 0.03 0.12 0.28 0.49 0.77)
             (6 0.02 0.09 0.20 0.36 0.57 0.82)
             (7 0.02 0.07 0.16 0.28 0.43 0.63 0.85)
             (8 0.01 0.06 0.12 0.22 0.34 0.49 0.67 0.88))
          )
         )
         ((= (strcase spacetype) "SIMP")
          (setq factlist '((1 0.25) (2 0.11 0.44) (3 0.06 0.25 0.56) (4 0.04 0.16 0.36 0.64)
                    (5 0.03 0.11 0.25 0.44 0.69) (6 0.02 0.08 0.18 0.33 0.51 0.74)
                    (7 0.02 0.06 0.14 0.25 0.39 0.56 0.77)
                    (8 0.01 0.05 0.11 0.20 0.31 0.44 0.61 0.79)
                    (9 0.01 0.04 0.09 0.16 0.25 0.36 0.49 0.64 0.81))
          )
         )      
    )
    (genip)          
    (drawbeam)
    (label)
    (dimspa)
    (command "style" "" "" "" 0.9 "" "" "" "")
    (setvar "filedia" 1)
    (if (/= omo nil)
       (setvar "osmode" omo)
    )
)     


(defun input ()
   (setq cgstype '(S s L l H h D d)) 
   (initget 1 "1 2")
   (setq ntenlay (atof (getkword "\nEnter 1 or 2 to designate number of tendon layers: ")))
   (initget  "10 12 20 simp SIMP")
   (setq spacetype (getkword "\nEnter 10,12,20 OR SIMP to designate type of support spacing [10]: "))
      (if (= spacetype  nil) (setq spacetype "10"))
   (setq beamdepth (getreal "Enter beam depth in inches: "))
   (setq ncgs 1)   
   (princ "\nEnter height & type of cgs no. ")(princ ncgs)
   (princ ", [example: 23.5S w/ S L H or D]")
   (setq cgs (getstring "\n[Stressed Low High Deadend]: "))
   (setq lastchar (substr cgs (strlen cgs) 1))
   (while (not (member (read lastchar) cgstype))
      (princ "\nPlease reenter height & type of cgs no. ")(princ ncgs)
      (setq cgs (getstring "\n[example: 23.5S w/ Stressed Low High Deadend]: "))
      (setq lastchar (substr cgs (strlen cgs) 1))
   ) 
   (if (or (= (strcase lastchar) "S") (= (strcase lastchar) "D"))
       (setq dend (getdist "Enter distance from CGS to end of beam: "))
       (setq dend 0)
   )    
   (setq d (getdist "Enter distance to next CGS:"))
                     ;INITIALIZE DATA LISTS
   (setq cgsdata (list lastchar))
   (setq cgsht (list (atof (substr cgs 1 (1- (strlen cgs))))))
   (setq dendata (list dend))
   (setq distdata (list d))
   (while (/= d 0 )
      (setq ncgs (1+ ncgs))
      (princ "\nEnter height & type of cgs no. ")(princ ncgs)(princ " or return if none: ")
      (princ " [example: 23S w/ S L H or D]")
      (setq cgs (getstring "\n[Stressed Low High Deadend]: "))
      (setq lastchar (substr cgs (strlen cgs) 1))
      (while (not (member (read lastchar) cgstype))
         (princ "\nPlease reenter height & type of cgs no. ")(princ ncgs)
         (setq cgs (getstring "\n[example: 23.5S w/ Stressed Low High Deadend]: "))
         (setq lastchar (substr cgs (strlen cgs) 1))
      )  
      (cond ((/= cgs "")
             (if (or (= (strcase lastchar) "S") (= (strcase lastchar) "D"))
                 (setq dend (getdist "Enter distance from CGS to end of beam: "))
                 (setq dend 0)
             )
             (princ "\nEnter distance from CGS no. ")(princ ncgs)
             (princ " to CGS no. ")(princ (1+ ncgs))
             (setq d (getdist "  [return if none]: "))
                 (if (not d) (setq d 0))
             (setq cgsdata (cons lastchar cgsdata))
             (setq cgsht (cons (atof (substr cgs 1 (1- (strlen cgs)))) cgsht))
             (setq dendata (cons dend dendata))
             (if (/= d 0 )
                (setq distdata (cons d distdata))) 
             
            )
      ) 
    )	
  (setq cgsdata (reverse cgsdata))
  (setq cgsht (reverse cgsht))
  (setq dendata (reverse dendata))
  (setq distdata (reverse distdata))
)
      
(defun genip ()
                  ;BEAM INSERTION POINTS
   (setq blength (+ (apply '+ dendata) (apply '+ distdata)))
   (setq bip (getpoint "Pick lower left beam corner: "))
   (setq blr (list (+ (car bip) blength) (cadr bip)))
   (setq bur (list (+ (car bip) blength) (+ (cadr bip) beamdepth)))
   (setq bul (list (car bip) (+ (cadr bip) beamdepth)))
                  ;INITIALIZE SPACING LIST 
   (setq spal '())
    
                  ;TENDON INSERTION POINTS
   (setq n 0)
                  ;INITIALIZE TENDON IP LIST
   (setq ipht1 (- (nth n cgsht) (* ntenlay 0.25)))     
   (setq tipl (list (list (car bip) (+ (cadr bip) ipht1))))
   
                ;SECOND TENDON INSERTION POINT
   (if (/= (nth n dendata) 0.0)
      (setq tipl (cons (list (+ (car bip) (nth n dendata)) 
                          (cadr (car tipl))) tipl))) 
   (while (< n (1- (length cgsdata)))
                  
                  ;DETERMINE DRAPE
       (setq drape (abs (- (nth n cgsht) (nth (1+ n) cgsht))))
      
                  ;DETERMINE NO. OF SPACES & SPACING
       (setq d (nth n distdata))
       (setq ns (/ d maxspa))
       (if (> (abs (- ns (fix ns))) 0.01) 
           (setq ns (1+ (fix ns)))
           (setq ns (fix ns))      
       )
       (setq spacing (/ d ns))
       (setq spal (cons (list ns spacing) spal))

                   ;DETERMINE TENDON IP
       (cond ((> (nth n cgsht) (nth (1+ n) cgsht))
              (setq fl (reverse (cdr (assoc (1- ns) factlist))))
              (setq lowpoint (+ (cadr bip) (nth (1+ n) cgsht)))
             )
             (T
              (setq fl (cdr (assoc (1- ns) factlist)))
              (setq lowpoint (+ (cadr bip) (nth n cgsht)))
             )
       )
       (setq i 0)
       (while (< i (1- ns))
          (setq x (+ (car (car tipl)) spacing))
          (setq y (- (+ lowpoint (* (nth i fl) drape))(* ntenlay 0.25)))
          (setq tipl (cons (list x y) tipl))
          (setq i (1+ i))
       )
                   ;ADD IP AT CGS
       (setq x (+ (car (car tipl)) spacing)) 
       (setq y (+ (cadr bip) (- (nth (1+ n) cgsht) (* ntenlay 0.25))))            
       (setq tipl (cons (list x y) tipl))
       (setq n (1+ n))          
   )
                    ;ADD LAST IP
   (cond ((/= (car dendata) 0.0)
          (setq lip (car tipl))
          (setq lip (list (+ (car lip) (car (reverse dendata)))
                         (cadr lip))
          )
          (setq tipl (cons lip tipl))
         )
   )
   (setq tipl (reverse tipl)) 
   (setq spal (reverse spal))            
)
   
(defun dimspa ()
               ;SET DIMENSION STYLE
   (command "dim" "restore" "tixoff" "e")
            ;SET DIMENSION LINE OFFSET
   (setq doff (list (car bul) (+ (cadr bul) scale)))

           ;DIMENSION ENDS OF BEAM IF CGS NOT AT ENDS
   (cond ((/= (car dendata) 0.0)
          (setq dipl (list (+ (car dendata) (car bul)) (cadr bul) ))
          (command "dim" "hor" dipl bul doff "" "" "e")
         )
         (T (setq dipl bul))
   )  
   (cond ((/= (last dendata) 0.0)
          (setq dipr (list (- (car bur)(last dendata))(cadr bur)))
          (command "dim" "hor" dipr bur doff "" "" "e")
         )
   )
                     ;INITIALIZE DIM IP
   (setq i 0)
   (setq lip dipl)
   (setq rip (list (+ (car dipl) (car distdata)) (cadr dipl)))
                ;LOOP TO DIMENSION SPACING
   (command "dim" "restore" "tixon" "e")  
   (while (< i (length spal))
                  ;DETERMINE IF ROUNDING UP, DOWN OR NONE
      (setq ns (car (nth i spal)))
      (setq s (rtos (cadr (nth i spal)) 5))
      (setq d (nth i distdata))
      (cond ((> (- d (* ns (distof s))) 0.1)
               (setq off "(+)")
            )
            ((> (- (* ns (distof s)) d) 0.1)
             (setq off "(-)")
            )
            (T (setq off ""))
      )
      (setq sdim (strcat (itoa ns) " spa @ " 
                         s "\"" off" = "
                         (rtos d 4)
                 )
      )
      (if (/= (car (nth i spal)) 1)                   
          (command "dim" "hor" lip rip doff sdim "e")
          (command "dim" "hor" lip rip doff "" "e")
      )
      (setq i (1+ i))
      (setq lip rip)
      (if (< i (length spal))
          (setq rip (list (+ (car rip) (nth i distdata)) (cadr rip)))
      )
   )
)      

(defun drawbeam ()  ;DRAW BEAM, TENDONS & SUPPORTS
   (command "pline" bip "w" 0.0 0.0 blr bur bul "c" "") ;DRAW BEAM
   (setq i 1)
   (setq sp (car tipl))
   (setq tenset (ssadd))
   (while (< i (length tipl))   ;DRAW TENDON
      (setq p (nth i tipl))
      (setq bp (list (car p) (cadr bip))) 
      (command "pline" sp p "")
      (setq tenset (ssadd (ssname (ssget "l") 0) tenset))
      (if (/= i (1- (length tipl)))    ;DRAW SUPPORT
              (command "line" p bp "" )
      )
      (setq sp p)
      (setq i (1+ i))
      (setq tenset (ssadd (ssname (ssget "l") 0) tenset))
   )
   (command "pedit" "l" "j" tenset "" "")
   
   (redraw)
) 

(defun label ()
               ;SET TEXT WIDTH TO 0.7
   (setvar "filedia" 0)
   (command "style" "ROMANS" "ROMANS,SPECIAL" "" 0.7 "" "" "" "")

   (setq n 1)
   (setq scarl '(("1/8" "~2") ("1/4" "~4") ("3/8" "~6") ("1/2" "~8")
                       ("5/8" "~0") ("3/4" "~w") ("7/8" "~r"))           
   )
   (setq beambot (cadr bip))
            ;LOOP TO LABEL SUPPORT HEIGHTS
   (while (< n (1- (length tipl)))
      (setq lab (- (cadr (nth n tipl)) beambot))
      ;(setq lab (* 0.125 (fix (/ lab 0.125)))) ROUND TO NEAREST 8TH RATHER THAN DOWN
                     ;INSERT SPECIAL CHARACTERS AT FRACTIONS
      (setq lab (spins lab))
     
      (setq labip (list (car (nth n tipl)) 
                        (- (cadr bip)(* 0.25 scale))))
      (command "text" "j" "m" labip "" lab)
      (setq n (1+ n))      
   )
   (setq n 0)
   (setq labip (list (+ (car bip) (car dendata))
                     (- (cadr bip)(* 0.50 scale))))
                      ;LOOP TO LABEL CGS'
   (while (< n (length cgsht))
      (setq lab (nth n cgsht))
                     ;INSERT SPECIAL CHARACTERS AT FRACTIONS
      (setq lab (spins lab))
      (setq lab (strcat lab "\" CGS"))
      (command "text" "j" "m" labip "" lab)
      (if (/= (nth n distdata) nil)
          (setq labip (list (+ (nth n distdata) (car labip)) 
                        (- (cadr bip)(* 0.50 scale))))
      )
      (setq n (1+ n))
   )                  
)
 
(defun spins (c) ;FUNCTION TO INSERT SPECIAL CHARACTERS @ FRACTIONS     
   (setq c (rtos lab 5 2))
         (if (/= (strlen c) 1)
            (if (= (substr c (1- (strlen c)) 1) "/")
                   (setq c (strcat (substr c 1 (- (strlen c) 4))
                                 (cadr (assoc (substr c (- (strlen c) 2) 3)
                                                scarl))
                           )
                   )
            )
         )
   (eval c)
)
