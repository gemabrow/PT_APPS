(defun c:chairbom ()
   ;PROGRAM TO READ ATTRIBUTE FILE (C:\ACADWIN\CCS\CHAIRBOM.TXT)
   ;AND TO WRITE A CHAIR BILL-OF-MATERIALS BACK TO DRAWING

;EXTRACT ATTRIBUTES
(setvar "FILEDIA" 0) 
(prompt "Please wait for processing of attributes")(terpri)
(setvar "CMDECHO" 0)
(command "attext" "" "f:\\apps\\CCS_CAD\\bom\\chairtem.txt" 
         "c:\\chairbom.txt")
(setvar "FILEDIA" 1)
(prompt "Please wait")(terpri)

(setq a (open "c:\\chairbom.txt" "r"))
(setq charlist 
   '("1" "2" "3" "4" "5" "6" "7" "8" "9" "0" "~" "/" "\"" "q" "w" "e" "r" "t"))
(setq scale (getvar "userr1"))
(setq chrhts '())
(setq alist '())
(listatt)
(close a)
(setq sp (getpoint "Pick starting point for chair schedule: "))
(printatt (length slist) 0 sp)
(setvar "CMDECHO" 1)
)

(defun listatt ()
   (while (setq l (read-line a))  
      (setq cl (proline l 1 nil nil ""))
      (if (not (member (car cl) chrhts))
          (progn
             (setq chrhts (cons (car cl) chrhts))
             (setq alist (cons cl alist))
          )
          (progn 
             (setq old (assoc (car cl) alist))
             (setq new (append old (cdr cl)))
             (setq alist (subst new old alist))
          )
      )
   )
   (setq slist '())
   (foreach x alist 
      (setq slist (cons (list (car x) (apply '+ (cdr x))) slist)))
)

(defun proline (l cn 2f h n / hnl cc )
   (setq cc (substr l cn 1))  
   (cond ((= cn (1+ (strlen l)))
          (setq hnl (list h (atoi n)))
         )
         ((and (member cc charlist) (not 2f))
          (if (= h nil)
              (setq h cc)
              (setq h (strcat h cc))
          )
          (proline l (1+ cn) nil h n)
         )
         ((= cc ",") (proline l (1+ cn) T h n))
         ((and (member cc charlist) 2f)
          (if (= n "")
              (setq n cc)
              (setq n (strcat n cc))
          )
          (proline l (1+ cn) T h n)
         )
         (T (proline l (1+ cn) 2f h n))
   )
) 
(defun printatt (n i sp)
   (setq l (car (nth i slist)))
   (command "text" sp "" l)
   (setq l (itoa (cadr (nth i slist))))
   (command "text" "@84<0" "" l)
   (setq sp (list (car sp) (- (cadr sp) (/ scale 3))))
   (setq i (1+ i))
   (if (< i n) (printatt n i sp))
)
