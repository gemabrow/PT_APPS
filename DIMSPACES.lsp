(defun c:dimspaces ()
                     

   (setq dl (list '("H" "hor") '("V" "vert") '("A" "aligned")))
   (initget "h H v V a A")
   (setq mode (strcase (getkword "Enter H, V or A for hor, vert or aligned dimensions: ")))
   (setq mode (cadr (assoc mode dl)))
   (setq p1 (getpoint "\nPick first point for space dimension: "))
   (while (eval 'p1)
     (setq p2 (getpoint "\nPick second point for space dimension: "))
     (setq p3 (getpoint "\nPick dimension location: "))
     (setq ns (getint "\nEnter number of spaces: "))
     (cond ((= mode "hor")
            (setq d (distance p1 (list (car p2) (cadr p1))))
           )
           ((= mode "vert")
            (setq d (distance p1 (list (car p1) (cadr p2))))
           )
           (T
            (setq d (distance p1 p2))
           )
     )
     (setq s (rtos (/ d ns) 4 3))
     (cond ((> (- d (* ns (distof s 4))) 0.1)
               (setq off "(+)")
            )
            ((> (- (* ns (distof s)) d) 0.1)
             (setq off "(-)")
            )
            (T (setq off ""))
      )
      (setq sdim (strcat (itoa ns) " SPA @ " 
                         s off)                               
      )
      (command "dim" mode p1 p2 p3 sdim "e")
      (setq p1 (getpoint "\nPick first point for space dimension, return to exit: "))
   )      
)
